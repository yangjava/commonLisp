(defun C:chcir1(/ ss txsize n index ent type oldsize newsize ent1)
 (setq ss (ssget))
 (setq txsize (getreal "\n输入比例系数:"))
 (setvar "cmdecho" 0)
 (setq n (sslength ss))
 (setq index 0)
 (repeat n
  (setq ent (entget (ssname ss index)))
  (setq index (+ 1 index))
  (setq type (assoc 2 ent))
  (if (or (= "AXI0" (cdr type)) (= "AXI" (cdr type)))
   (progn
    (setq oldsize1 (assoc 41 ent))
    (setq oldsize2 (assoc 42 ent))
    (setq newsize1 (cons (car oldsize1) txsize))
    (setq newsize2 (cons (car oldsize2) txsize))
    (setq ent1 (subst newsize1 oldsize1 ent))
    (setq ent2 (subst newsize2 oldsize2 ent1))
    (entmod ent2)
   )
  )
 )
; (redraw)
(setvar "cmdecho" 1)
)
