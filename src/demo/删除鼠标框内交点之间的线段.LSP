(defun c:eb()     ;erase box
    (setvar "cmdecho" 0 )
    (setvar "osmode"  0 )
    (setvar "regenmode" 0)
    (command "layer" "off" "cen" "")
    (command "layer" "off" "dqx" "")
    (setq pt1 (getpoint "\n???:"))
    (setq pt2 (getcorner pt1 "\n???:"))
(while ( or (not(eq pt1 nil))(not(eq pt2 nil)))
    (setq s nil)
    (setq s(ssget "c" pt1 pt2))
    (while (= s nil)
           (progn
              (alert "???????????????!")
              (setq pt1 (getpoint "\n???:"))
              (setq pt2 (getcorner pt1 "\n???:"))
              (setq s(ssget "c" pt1 pt2))
           )
    )
    (if (> (sslength s) 25)
        (progn
             (alert "??????????!!!!")
             (quit)
         )
    )
    ;(princ "\n???????????????,?????:")
    ;(setq s_w (ssget))
    ;(if (= s_w nil)
    ;    (setq s_w (ssadd))
    ;)
    (setq max_x(max (car  pt1) (car  pt2)) 
          max_y(max (cadr pt1) (cadr pt2))
          min_x(min (car  pt1) (car  pt2))
          min_y(min (cadr pt1) (cadr pt2))
    )
    
    (setq sline (ssadd))
    (setq i0 0)
    (while (ssname s i0)
           (if (= (cdr (assoc 0 (entget (ssname s i0)))) "LINE") 
               (ssadd (ssname s i0) sline)
           )
           (setq i0 (+ i0 1 )) 
    )
    (setq int_list (list))
    (while (ssname sline 0)
           (setq pta  (cdr (assoc 10 (entget (ssname sline 0)))))
           (setq ptb  (cdr (assoc 11 (entget (ssname sline 0)))))
           (ssdel (ssname sline 0) sline)
           (setq k 0)
           (while (ssname sline k)
                  (setq ptk1  (cdr (assoc 10 (entget (ssname sline k)))))
                  (setq ptk2  (cdr (assoc 11 (entget (ssname sline k)))))
                  (setq int(inters pta ptb ptk1 ptk2 ))
                  (if (and ( > (car  int) min_x)
                           ( < (car  int) max_x) 
                           ( > (cadr int) min_y)
                           ( < (cadr int) max_y)
                      )
                      (setq int_list(cons int int_list))
                  )
                  (setq k (+ k 1))
           )
     )

     (setq a        (car int_list))
     (while a
           (setq a1(list(+(car a) 0.00000000001)(+(cadr a) 0.00000000001)))
           (setq a2(list(-(car a) 0.00000000001)(-(cadr a) 0.00000000001)))
           (setq vl (ssget "c" a1 a2 ))
           (setq ii 0)
           (while (ssname vl ii)
                  ;(if (not(ssmemb(ssname vl ii) s_w))
                     ; (progn
                         (setq ent (ssname vl ii))
                         (command "break" ent a "@")
                      ;)
                  ;)
                  (setq ii (+ ii 1 ))
           )
           (setq int_list (cdr int_list))
           (setq a        (car int_list))
      )
           
      (setq del_line (ssget "w" pt1 pt2))
      (if del_line
          (command "erase" del_line "")
       )
       (setq pt1 (getpoint "\n???:"))
       (if (eq pt1 nil)
          (setq pt2 nil)
          (setq pt2 (getcorner pt1 "\n???:"))
       )
);while
      (command "layer" "on" "cen" "")
      (command "layer" "on" "dqx" "")
      (setvar "regenmode" 0)
      (SETVAR "OSMODE" 32)
      (REDRAW)
      (princ "\n????.????")
      (princ)
)
