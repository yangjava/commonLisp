(defun c:test ( / ss)
  (vl-load-com)
  (setq entlay (entsel "\nSelect object on layer to copy from: "))
  (setq objlay (vla-get-layer (vlax-ename->vla-object (car entlay))))
  (prompt "\nSelect Texts: ")
  (setq ss (ssget))
  (setq n 0)
  (while (< n (sslength ss))
    (vla-put-layer (vlax-ename->vla-object (ssname ss n)) objlay)
    (setq n (1+ n))
  )
)
