(VMON)
;
(setq factor 1)
(command "layer" "m" "pdim" "c" "green" "" "")
(command "layer" "m" "rei" "c" "1" "" "s" "0" "")
;
(defun intp(ntype p0 p1 R)
 (if (< (distance p0 p1) R)
     (progn
          (setq xx0 (nth 0 p0)
                yy0 (nth 1 p0)
                x  (nth 0 p1)
                y  (nth 1 p1)
                RR (* R R)
                ydd (* (- y yy0) (- y yy0))
                xdd (* (- x xx0) (- x xx0))
                xd (sqrt (- RR ydd))          
                yd (sqrt (- RR xdd))
          ) ;setq end
          (setq x (if (= ntype 1) (+ xx0 xd) x)
                y (if (= ntype 2) (+ yy0 yd) y)
          )      
          (setq p (list x y)
          ) ;setq end
     ) ;progn end
     (setq p p1)
 ) ;if end
) ;defun end
;
(defun C:BKJC()
 (setvar "cmdecho" 0)
 (setvar "dimlfac" (/ 1.0 factor))
 (setq oer *error* *error* clmerr)
 (setq scale0 (getvar "userr1"))
 (command "layer" "s" "0" "")
      (setq scale0 (getvar "userr1"))
      (setq l1 (+ L (* 30 scale))      
            l2 (+ h1 a1 B (* 100 scale))
      ) ;setq end
      (princ "\n基础插入点:")
      (command "insert" "border" "x" l1 "y" l2 "r" 0 pause)
      (command "erase" "l" "")
   (if (= type_bk 1) 
     (progn 
      (setq p01 (getvar "lastpoint")
            p02 (polar p01 0 (+ (/ L 2.0) (* 30 scale)))
            p02 (polar p02 pi09 (+ h1 a1 (* 150 factor) (* 20 scale)))
            p03 (polar p02 pi09 (+ (/ A 2.0) (* 60 scale)))
      ) ;setq end
      (pim-1 p03)
      (pom-1 p02)
     ) ;progn end
     (progn 
      (setq p01 (getvar "lastpoint")
            p02 (polar p01 0 (+ (/ L 2.0) (* 30 scale)))
            p02 (polar p02 pi09 (+ h1 a1 (* 150 factor) (* 20 scale)))
            p03 (polar p02 pi09 (+ (/ A 2.0) (* 60 scale)))
      ) ;setq end
      (pim-2 p03)
      (pom-2 p02)
     ) ;progn end
   ) ;if end   
   (setvar "dimlfac" 1.0)
   (command "layer" "s" "0" "")
   (setvar "dimlfac" 1)
) ;JC2 end
;
(defun pim-1(p0)
       (command "layer" "s" "0" "")
       (setq AA  A
             BB  L
             AA2 (/ AA 2.0)
             BB2 (/ BB 2.0)
             p41 (polar p0 pi18 BB2)
             p41 (polar p41 pi27 AA2)
             p42 (polar p41 0 BB)
             p43 (polar p42 pi09 AA)
             p44 (polar p41 pi09 AA)
             R (if (> AA2 BB2) BB2 AA2)
             R (* 0.5 R)
       ) ;setq end    
       (command "line" p41 p42 p43 p44 "c")
; draw arc       
       (setq p1 (polar p41 0 R)
             p2 (polar p41 pi09 R)
       )
       (command "arc" "c" p41 p1 p2)
;draw collumn
       (setq AA2 (/ b 2.0)
             BB2 (/ h 2.0)
             p31 (polar p0 pi18 BB2)
             p31 (polar p31 pi27 AA2)
             p32 (polar p31 0 h)
             p33 (polar p32 pi09 b)
             p34 (polar p31 pi09 b)
        ) ;setq end
       (command "linetype" "s" "dashed2" "")
       (command "line" p31 p32 p33 p34 "c")
       (command "linetype" "s" "bylayer" "")
       (setq AA2 (+ (/ b 2.0) (* 25 factor))
             BB2 (+ (/ h 2.0) (* 25 factor))
             p51 (polar p0 pi18 BB2)
             p51 (polar p51 pi27 AA2)
             p52 (polar p51 0 (* BB2 2.0))
             p53 (polar p52 pi09 (* 2.0 AA2))
             p54 (polar p51 pi09 (* 2.0 AA2))
        ) ;setq end
       (command "line" p51 p52 p53 p54 "c")
       (setq AA2 (+ (/ b 2.0) (* 75 factor))
             BB2 (+ (/ h 2.0) (* 75 factor))
             p31 (polar p0 pi18 BB2)
             p31 (polar p31 pi27 AA2)
             p32 (polar p31 0 (* BB2 2.0))
             p33 (polar p32 pi09 (* 2.0 AA2))
             p34 (polar p31 pi09 (* 2.0 AA2))
        ) ;setq end
       (command "line" p31 p32 p33 p34 "c")
       (command "line" p31 p51 "")
       (command "line" p32 p52 "")
       (command "line" p33 p53 "")
       (command "line" p34 p54 "")
       (setq AA2 (+ (/ b 2.0) (* 75 factor) t)
             BB2 (+ (/ h 2.0) (* 75 factor) t)
             p31 (polar p0 pi18 BB2)
             p31 (polar p31 pi27 AA2)
             p32 (polar p31 0 (* BB2 2.0))
             p33 (polar p32 pi09 (* 2.0 AA2))
             p34 (polar p31 pi09 (* 2.0 AA2))
        ) ;setq end
       (command "line" p31 p32 p33 p34 "c")
       (command "line" p42 p32 "")
       (command "line" p43 p33 "")
       (command "line" p44 p34 "")
       (setq ang (angle p41 p31)
             pp (polar p41 ang R)
       ) ;setq end
       (command "line" pp p31 "")
; draw reinforcement       
       (command "layer" "s" "rei" "")
       (setq scale0 (getvar "userr1")
             dx (* 1 scale0)
             dy dx
             x41 (nth 0 p41)
             y41 (nth 1 p41)
             xr0 (+ x41 dx)
             yr0 (+ y41 dy)
             n (fix (/ (- R dx) (* 5 scale0)))
             index 0
        ) ;setq end     
        (repeat (1+ n)
            (setq dx (* index (* 5 scale0))
                  dy dx
                  index (1+ index)
                  x1 (+ xr0 dx)
                  y1 (+ yr0 dy)
                  po1 (list x1 yr0)
                  po2 (intp 2 p41 po1 R)
                  po3 (list xr0 y1)
                  po4 (intp 1 p41 po3 R)
            ) ;setq end
            (command "line" po1 po2 "")
            ;-------
            ;(princ "\n draw rei line")
            ;(princ index) (getstring "\npress any key to continue")
            ;------
            (command "line" po3 po4 "")
        ) ;repeat end
;draw rei num1
        (command "layer" "s" "0" "")
        (setq dx (* 2.5 scale0)
              dy dx
              pr0 (list xr0 yr0)
              p1 (polar pr0 0 dx)
              p1 (polar p1 pi27 (* 10 scale0))
              p2 (polar po3 0 dx)
              p2 (polar p2 pi09 (* 2 scale0))
              p3 (polar p1 pi18 (* 20 scale0))
              pc (polar p3 pi18 (* 4 scale0))
              pr (* 4 scale0)
              htext (* 4 scale0)
         ) ;setq end
         (command "line" p2 p1 p3 "")
         (command "circle" pc pr)
         (command "text" "j" "m" pc htext 0 "2")
;draw rei num2
        (setq dx (* 2.5 scale0)
              dy dx
              pr0 (list xr0 yr0)
              p1 (polar pr0 pi09 dy)
              p1 (polar p1 pi18 (* 10 scale0))
              p2 (polar po1 90 dx)
              p2 (polar p2 0 (* 2 scale0))
              p3 (polar p1 pi09 (* 20 scale0))
              pc (polar p3 pi09 (* 4 scale0))
         ) ;setq end
         (command "line" p2 p1 p3 "")
         (command "circle" pc pr)
         (command "text" "j" "m" pc htext 90 "1")
;draw axis
         (setq AA2 (/ AA 2.0)
               BB2 (/ BB 2.0)
               p1 (polar p0 0 (+ BB2 (* 5 scale0)))
               p2 (polar p0 pi18 (+ BB2 (* 40 scale0)))
               p3 (polar p0 pi27 (+ AA2 (* 35 scale0)))
               p4 (polar p0 pi09 (+ AA2 (* 5 scale0)))
               rr (* 5 scale0)
               pc1 (polar p2 pi18 rr)  
               pc2 (polar p3 pi27 rr)
          ) ;setq end
          (command "layer" "s" "pdim" "")
          (command "line" p1 p2 "")
          (command "change" "l" "" "p" "lt" "axis" "")
          (command "line" p3 p4 "")
          (command "change" "l" "" "p" "lt" "axis" "")
          (command "circle" pc1 rr)          
          (command "circle" pc2 rr)
;draw dimension
         (command "layer" "s" "pdim" "")
         (setvar "dimdli" 0)
         ;(princ "\ndim1")
         (setq d1 (polar p41 pi18 (* 25 scale))         
               d2 (polar d1 pi09 (/ AA 2.0))
               d3 (polar d2 pi09 (/ AA 2.0))
               dp (polar d3 pi18 (* 10 scale))
         ) ;setq end
         (command "dim" "ver" d1 d2 dp "" "con" d3 "" "e")
         (setq temp b
               b h
               h temp
         ) ;setq end
         (setq dp d2
               d2 (polar d2 0 (* 10 scale))
               d1 (polar d2 pi27 (/ h 2.0))
               d3 (polar d2 pi09 (/ h 2.0))
         ) ;setq end
         (command "dim" "ver" d1 d2 dp "" "con" d3 "" "e")
        ;dim2
         (setq d1 (polar p41 pi27 (* 20 scale))         
               d2 (polar d1 0 (/ BB 2.0))
               d3 (polar d2 0 (/ BB 2.0))
               dp (polar d3 pi27 (* 10 scale))
         ) ;setq end
         (command "dim" "hor" d1 d2 dp "" "con" d3 "" "e")
         (setq dp d2
               d2 (polar d2 pi09 (* 10 scale))
               d1 (polar d2 pi18 (/ b 2.0))
               d3 (polar d2 0 (/ b 2.0))
         ) ;setq end                  
         (command "dim" "hor" d1 d2 dp "" "con" d3 "" "e")
   (command "layer" "s" "0" "")
) ;defun end
;      
;
(defun jc3_dash(p_dash b_dash / p_p1 delta p_p3 p_p4 p_p5 p_p6)
 (setq p_p1 (polar p_dash pi18 (+ (/ b 2) (* 2 scale)))
       delta (/ b_dash 3.0)
       p_p2 (polar p_p1 0 (+ (* 2 scale) delta))
       p_p3 (polar p_p2 0 (/ delta 2.0))
       p_p3 (polar p_p3 (* pi09 0.5) (* 6 scale))
       p_p5 (polar p_p2 0 delta)
       p_p4 (polar p_p5 pi18 (/ delta 2.0))
       p_p4 (polar p_p4 (* pi09 -1.5) (* 6 scale))
       p_p6 (polar p_p5 0 (+ delta (* 2 scale)))
 ) ;setq end
 (command "line" p_p1 p_p2 p_p3 p_p4 p_p5 p_p6 "")
) ;defun end
;
(defun  pom-1(p0)
       (jc3_dash p0 b)
       (setq x0 (nth 0 p0)
             y0 (nth 1 p0)
             pi09 (* pi 0.5)
             pi18 pi
             pi27 (* pi 1.5)
             scale0 (getvar "userr1")
        ) ;setq end
        (setq p20 (polar p0 pi18 (/ b 2.0))
              p21 (polar p20 pi27 (* 25 scale))
              p22 (polar p21 pi27 h1)
              p23 (polar p22 0 (/ b 2.0))
              p25 (polar p23 pi27 (* 50 factor))
              p24 (polar p25 pi18 (+ (/ b 2.0) (* 50 factor)))
              p1  (polar p21 pi18 (* 75 factor))
              p2  (polar p1 pi18 t)
              p3  (polar p2 pi27 h2)
              p9  (polar p25 pi27 a1)
              p8  (polar p9  pi27 (* 100 factor))
              p5  (polar p9 pi18 (/ l 2.0))
              p6  (polar p5 pi18 (* 100 factor))
              p7  (polar p6 pi27 (* 100 factor))
              p4  (polar p5 pi09 a2)
        ) ;setq end
        (setvar "dimdli" 0)
        (command "layer" "s" "0" "")
        (command "line" p20 p22 p23 "")
        (command "line" p25 p24 p1 p2 p3 p4 p5 "")
        (command "line" p9 p6 p7 p8 "")
        (command "layer" "s" "pdim" "")
        (setq d1 (polar p7 pi18 (* 3 scale0))
              d2 (polar d1 pi09 (* 100 factor))
              d3 (polar d2 pi09 a2)
              dis (- (+ h1 a1 (* 50 factor)) a2 h2)
              d4 (polar d3 pi09 dis)
              d5 (polar d4 pi09 h2)
              dp (polar d1 pi18 (* 10 scale0))
         )
         (command "dim" "ver" d1 d2 dp "" "con" d3 "" "ver" d4 d5 dp "" "e")
         (setq d1 (Polar p9 0 (+ (/ b 2.0) t (* 5 scale)))
               d2 (Polar d1 pi09 a1)
               d3 (polar d2 pi09 (* 50 factor))
               d4 (polar d3 pi09 h1)
               dp (polar d1 0 (* 10 scale))
         ) ;setq end
         (command "dim" "ver" d1 d2 dp "" "con" d3 "" "con" d4 "" "e")
         (setq p_bg (polar p6 pi18 (* 25 scale0))
               sc_x (/ scale0 100.0)
               sc_y sc_x
         )
         (command "insert" "elul" p_bg sc_x sc_y 0 bg)
         (setq p13 (polar p5 0 (* 2.0 scale0))
               p13 (polar p13 pi09 (* 3.0 scale0))
               p14 (polar p9 pi09 (* 3.0 scale0))
               p18 (polar p21 0 (/ b 2.0))
         ) ;setq end
         (command "layer" "s" "rei" "")
         (command "line" p13 p14 "")
         (command "layer" "s" "pdim" "")
         (setq d1 (polar p24 pi27 (* 3 scale))
               d2 (polar d1 0 (* 50 factor))
               dp (polar d1 pi27 (* 10 scale))
         ) ;setq end
         (command "dim1" "hor" d1 d2 dp "")
         (setq d1 (Polar p21 pi09 (* 5 scale))
               d2 (polar d1 0 b)
               d3 (polar d2 0 (* 75 factor))
               d4 (polar d3 0 t)
               dp (polar d1 pi09 (* 10 scale))
         ) ;setq end
         (command "dim" "hor" d1 d2 dp "" "con" d3 "" "con" d4 "" "e")
         (command "mirror" "c" p7 p18 "" p8 p18 "n")
;         
         (setq d1 (polar p7 pi27 (* 5.0 scale0))
               d2 (polar d1 0 (* 100 factor))
               dp (polar d1 pi27 (* 10 scale0))
               pdo (polar p13 pi27 (* 1.0 scale0))
               xd (* 5 scale0)
               rd (* 1 scale0)
         ) ;setq end
         (command "layer" "s" "pdim" "")
         (command "dim1" "hor" d1 d2 dp "")
         (command "layer" "s" "0" "")
         (command "donut" 0 rd pdo "")
         (command "array" "l" "" "r" 1 6 xd)
         (setq p1 (polar pdo 0 (* 15 scale0))
               p2 (polar p1 pi27 (* 15 scale0))
               pc (polar p2 pi27 (* 4 scale0))
               rr (* 4.0 scale0)
               htext (* 4 scale0)
         )
         (command "line" p1 p2 "")
         (command "circle" pc rr)
         (command "text" "j" "m" pc htext 0 "1")
         (setq p1 (polar p13 0 (* 0.7 L))
               p2 (polar p1 pi27 (* 15 scale0))
               pc (polar p2 pi27 (* 4 scale0))
         )
         (command "line" p1 p2 "")
         (command "circle" pc rr)
         (command "text" "j" "m" pc htext 0 "2")
         (setq p1 (polar p8 pi27 (* 15 scale0))
               p2 (polar p0 pi09 (* 5 scale0))
               pc (polar p1 pi27 (* 5 scale0))
               rr (* 5.0 scale0)
         )
         (command "line" p1 p2 "")
         (command "circle" pc rr)
         (command "layer" "s" "0" "")
         (command "linetype" "s" "bylayer" "")
) ;defun end
;--------
(defun C:bkCS( / lx llx lly p0 p1)
 (setvar "cmdecho" 0)
 (setq lx_pim '(2500 3650)
       ly_pim '(2200 2150)
       lx_pom '(3720 4700)
       ly_pom '(2320 2430)
       lx (/ scale 20.0)
 ) ;setq end
 (command "zoom" "a")
 (princ "\n例图插入点:")
 (setq llx (* lx (nth (1- type_bk) lx_pim))
       lly (* lx (nth (1- type_bk) ly_pim))
 ) ;setq end
 (command "insert" "border" "x" llx "y" lly "r" 0 pause)
 (command "erase" "l" "")
 (setq p0 (getvar "lastpoint")
       p1 (polar p0 0 llx)
       p1 (polar p1 pi09 lly)
 ) ;setq end
 (command "zoom" "w" p0 p1)
 (if (= type_bk 1)
     (command "insert" "pim-k1" p0 lx lx 0)
     (command "insert" "pim-k2" p0 lx lx 0)
 ) ;if end
 (Setq L (getreal "\nL:(mm)")
       A (getreal "\nB:(mm)")
       b (getreal "\nb:(mm)")
       h (getreal "\nh:(mm)")
       L (* factor L)
       A (* factor A)
       b (* factor b)
       h  (* factor h)
 ) ;setq end
 (command "erase" "l" "")
 (setq llx (* lx (nth (1- type_bk) lx_pom))
       lly (* lx (nth (1- type_bk) ly_pom))
 ) ;setq end
 (setq p1 (polar p0 0 llx)
       p1 (polar p1 pi09 lly)
 ) ;setq end
 (command "zoom" "w" p0 p1)
 (if (= type_bk 1)
     (command "insert" "pom-k1" p0 lx lx 0)
     (command "insert" "pom-k2" p0 lx lx 0)
 ) ;if end
 (setq a1 (getreal "\na1:(mm)")
       h1 (getreal "\nh1:(mm)")
       a2 (getreal "\na2:(mm)")
       h2 (getreal "\nh2:(mm)")
       t  (getreal "\nt:(mm)")
       a1 (* factor a1)
       a2 (* factor a2)
       h1 (* factor h1)
       h2 (* factor h2)
       t  (* factor t)
       bg (getstring "\n基础底标高:(m)")
 ); setq end
 (if (= type_bk 2)
     (Setq d (getreal "\nd:(mm)")
           d (* factor d)
     ) ;setq end
 ) ;if end
 (command "erase" "l" "")
 (command "zoom" "a")
 (setvar "cmdecho" 1)
) ;defun end
;
(defun pim-2(p0)
       (command "layer" "s" "0" "")
       (setq AA  A
             BB  L
             AA2 (/ AA 2.0)
             BB2 (/ BB 2.0)
             p41 (polar p0 pi18 BB2)
             p41 (polar p41 pi27 AA2)
             p42 (polar p41 0 BB)
             p43 (polar p42 pi09 AA)
             p44 (polar p41 pi09 AA)
             R (if (> AA2 BB2) BB2 AA2)
             R (* 0.5 R)
       ) ;setq end    
       (command "layer" "s" "0" "")
       (command "line" p41 p42 p43 p44 "c")
; draw arc       
       (setq p1 (polar p41 0 R)
             p2 (polar p41 pi09 R)
       )
       (command "arc" "c" p41 p1 p2)
;draw collumn
       (setq AA2 (/ b 2.0)
             BB2 (/ h 2.0)
             pp0 (polar p0 pi18 (/ d 2.0))
             p31 (polar pp0 pi18 BB2)
             p31 (polar p31 pi27 AA2)
             p32 (polar p31 0 h)
             p33 (polar p32 pi09 b)
             p34 (polar p31 pi09 b)
        ) ;setq end
       (command "linetype" "s" "dashed2" "")
       (command "line" p31 p32 p33 p34 "c")
       (command "linetype" "s" "bylayer" "")
       (setq AA2 (+ (/ b 2.0) (* 25 factor))
             BB2 (+ (/ h 2.0) (* 25 factor))
             p51 (polar pp0 pi18 BB2)
             p51 (polar p51 pi27 AA2)
             p52 (polar p51 0 (* BB2 2.0))
             p53 (polar p52 pi09 (* 2.0 AA2))
             p54 (polar p51 pi09 (* 2.0 AA2))
        ) ;setq end
       (command "line" p51 p52 p53 p54 "c")
       (setq AA2 (+ (/ b 2.0) (* 75 factor))
             BB2 (+ (/ h 2.0) (* 75 factor))
             p31 (polar pp0 pi18 BB2)
             p31 (polar p31 pi27 AA2)
             p32 (polar p31 0 (* BB2 2.0))
             p33 (polar p32 pi09 (* 2.0 AA2))
             p34 (polar p31 pi09 (* 2.0 AA2))
             p_1 (polar p0 pi27 100)
        ) ;setq end
       (command "line" p31 p32 p33 p34 "c")
       (command "line" p31 p51 "")
       (command "line" p32 p52 "")
       (command "line" p33 p53 "")
       (command "line" p34 p54 "")
       (command "mirror" "c" p31 p33 "" p0 p_1 "n")
       (setq AA2 (+ (/ b 2.0) (* 75 factor) t)
             BB2 (+ (/ h 2.0) (* 75 factor) t (/ d 2.0))
             p31 (polar p0 pi18 BB2)
             p31 (polar p31 pi27 AA2)
             p32 (polar p31 0 (* BB2 2.0))
             p33 (polar p32 pi09 (* 2.0 AA2))
             p34 (polar p31 pi09 (* 2.0 AA2))
        ) ;setq end
       (command "line" p31 p32 p33 p34 "c")
       (command "line" p42 p32 "")
       (command "line" p43 p33 "")
       (command "line" p44 p34 "")
       (setq ang (angle p41 p31)
             pp (polar p41 ang R)
       ) ;setq end
       (command "line" pp p31 "")
; draw reinforcement       
       (command "layer" "s" "rei" "")
       (setq scale0 (getvar "userr1")
             dx (* 1 scale0)
             dy dx
             x41 (nth 0 p41)
             y41 (nth 1 p41)
             xr0 (+ x41 dx)
             yr0 (+ y41 dy)
             n (fix (/ (- R dx) (* 5 scale0)))
             index 0
        ) ;setq end     
        (repeat (1+ n)
            (setq dx (* index (* 5 scale0))
                  dy dx
                  index (1+ index)
                  x1 (+ xr0 dx)
                  y1 (+ yr0 dy)
                  po1 (list x1 yr0)
                  po2 (intp 2 p41 po1 R)
                  po3 (list xr0 y1)
                  po4 (intp 1 p41 po3 R)
            ) ;setq end
            (command "line" po1 po2 "")
            ;-------
            ;(princ "\n draw rei line")
            ;(princ index) (getstring "\npress any key to continue")
            ;------
            (command "line" po3 po4 "")
        ) ;repeat end
;draw rei num1
        (command "layer" "s" "0" "")
        (setq dx (* 2.5 scale0)
              dy dx
              pr0 (list xr0 yr0)
              p1 (polar pr0 0 dx)
              p1 (polar p1 pi27 (* 10 scale0))
              p2 (polar po3 0 dx)
              p2 (polar p2 pi09 (* 2 scale0))
              p3 (polar p1 pi18 (* 20 scale0))
              pc (polar p3 pi18 (* 4 scale0))
              pr (* 4 scale0)
              htext (* 4 scale0)
         ) ;setq end
         (command "line" p2 p1 p3 "")
         (command "circle" pc pr)
         (command "text" "j" "m" pc htext 0 "2")
;draw rei num2
        (setq dx (* 2.5 scale0)
              dy dx
              pr0 (list xr0 yr0)
              p1 (polar pr0 pi09 dy)
              p1 (polar p1 pi18 (* 10 scale0))
              p2 (polar po1 90 dx)
              p2 (polar p2 0 (* 2 scale0))
              p3 (polar p1 pi09 (* 20 scale0))
              pc (polar p3 pi09 (* 4 scale0))
         ) ;setq end
         (command "line" p2 p1 p3 "")
         (command "circle" pc pr)
         (command "text" "j" "m" pc htext 90 "1")
;draw axis
         (setq AA2 (/ AA 2.0)
               BB2 (/ BB 2.0)
               p1 (polar p0 0 (+ BB2 (* 5 scale0)))
               p2 (polar p0 pi18 (+ BB2 (* 40 scale0)))
               p3_1 (polar pp0 pi27 (+ AA2 (* 35 scale0)))
               p4_1 (polar pp0 pi09 (+ AA2 (* 5 scale0)))
               pp0 (Polar pp0 0 d)
               p3_2 (polar pp0 pi27 (+ AA2 (* 35 scale0)))
               p4_2 (polar pp0 pi09 (+ AA2 (* 5 scale0)))
               rr (* 5 scale0)
               pc1 (polar p2 pi18 rr)  
               pc2 (polar p3_1 pi27 rr)
               pc3 (polar p3_2 pi27 rr)
          ) ;setq end
          (command "layer" "s" "pdim" "")
          (command "line" p1 p2 "")
          (command "change" "l" "" "p" "lt" "axis" "")
          (command "line" p3_1 p4_1 "")
          (command "change" "l" "" "p" "lt" "axis" "")
          (command "line" p3_2 p4_2 "")
          (command "change" "l" "" "p" "lt" "axis" "")
          (command "circle" pc1 rr)          
          (command "circle" pc3 rr)          
          (command "circle" pc2 rr)
;draw dimension
         (command "layer" "s" "pdim" "")
         (setvar "dimdli" 0)
         ;(princ "\ndim1")
         (setq d1 (polar p41 pi18 (* 25 scale))         
               d2 (polar d1 pi09 (/ AA 2.0))
               d3 (polar d2 pi09 (/ AA 2.0))
               dp (polar d3 pi18 (* 10 scale))
         ) ;setq end
         (command "dim" "ver" d1 d2 dp "" "con" d3 "" "e")
         (setq temp b
               b h
               h temp
         ) ;setq end
         (setq dp d2
               d2 (polar d2 0 (* 10 scale))
               d1 (polar d2 pi27 (/ h 2.0))
               d3 (polar d2 pi09 (/ h 2.0))
         ) ;setq end
         (command "dim" "ver" d1 d2 dp "" "con" d3 "" "e")
        ;dim2
         (setq d1 (polar p41 pi27 (* 20 scale))         
               dd2 (polar d1 0 (/ BB 2.0))
               d2 (polar d1 0 (/ (- BB d) 2.0))
               d3 (polar d2 0 d)
               d4 (polar d3 0 (/ (- BB d) 2.0))
               dp (polar d3 pi27 (* 10 scale))
         ) ;setq end
         (command "dim" "hor" d1 d2 dp "" "con" d3 "" "con" d4 "" "e")
         (setq dp dd2
               d2 (polar dd2 pi09 (* 10 scale))
               d2 (polar d2 pi18 (/ d 2.0))
               d1 (polar d2 pi18 (/ b 2.0))
               d3 (polar d2 0 (/ b 2.0))
         ) ;setq end                  
         (command "dim" "hor" d1 d2 dp "" "con" d3 "" "e")
         (command "mirror" "c" d1 d3 "" p0 dp "n")
   (command "layer" "s" "0" "")
) ;defun end
;      
(defun  pom-2(p0)
       (jc3_dash (polar p0 pi18 (/ d 2.0)) b)
       (jc3_dash (polar p0 0 (/ d 2.0)) b)
       (setq x0 (nth 0 p0)
             y0 (nth 1 p0)
         pi09 (* pi 0.5)
             pi18 pi
             pi27 (* pi 1.5)
             scale0 (getvar "userr1")
        ) ;setq end
        (setq p20 (polar p0 pi18 (/ b 2.0))
              p20 (polar p20 pi18 (/ d 2.0))
              p30 (polar p20 0 b)
              p21 (polar p20 pi27 (* 25 scale))
              p22 (polar p21 pi27 h1)
              p23 (polar p22 0 (/ b 2.0))
              p25 (polar p23 pi27 (* 50 factor))
              p24 (polar p25 pi18 (+ (/ b 2.0) (* 50 factor)))
              p26 (polar p22 0 b)
              p27 (polar p26 0 (* 50 factor))
              p27 (polar p27 pi27 (* 50 factor))
              p1  (polar p21 pi18 (* 75 factor))
              p2  (polar p1 pi18 t)
              p3  (polar p2 pi27 h2)
              p9  (polar p25 pi27 a1)
              p8  (polar p9  pi27 (* 100 factor))
              p5  (polar p9 pi18 (/ l 2.0))
              p6  (polar p5 pi18 (* 100 factor))
              p7  (polar p6 pi27 (* 100 factor))
              p4  (polar p5 pi09 a2)
              p28 (polar p1 0 (+ b (* 150 factor)))
              p29 (polar p21 0 (+ (/ (+ d b) 2.0)))
              p9  (polar p9 0 (/ d 2.0))
              p8  (polar p8 0 (/ d 2.0))
        ) ;setq end
        (setvar "dimdli" 0)
        (command "layer" "s" "0" "")
        (command "line" p20 p22 p26 p30 "")
        (command "line" p29 p28 p27 p24 p1 p2 p3 p4 p5 "")
        (command "line" p9 p6 p7 p8 "")
        (command "layer" "s" "pdim" "")
        (setq d1 (polar p7 pi18 (* 3 scale0))
              d2 (polar d1 pi09 (* 100 factor))
              d3 (polar d2 pi09 a2)
              dis (- (+ h1 a1 (* 50 factor)) a2 h2)
              d4 (polar d3 pi09 dis)
              d5 (polar d4 pi09 h2)
              dp (polar d1 pi18 (* 10 scale0))
         )
         (command "dim" "ver" d1 d2 dp "" "con" d3 "" "ver" d4 d5 dp "" "e")
         (setq d1 (Polar p9 0 (+ d (/ b 2.0) t (* 5 scale)))
               d2 (Polar d1 pi09 a1)
               d3 (polar d2 pi09 (* 50 factor))
               d4 (polar d3 pi09 h1)
               dp (polar d1 0 (* 10 scale))
         ) ;setq end
         (command "dim" "ver" d1 d2 dp "" "con" d3 "" "con" d4 "" "e")
         (setq p_bg (polar p6 pi18 (* 25 scale0))
               sc_x (/ scale0 100.0)
               sc_y sc_x
         )
         (command "insert" "elul" p_bg sc_x sc_y 0 bg)
         (setq p13 (polar p5 0 (* 2.0 scale0))
               p13 (polar p13 pi09 (* 3.0 scale0))
               p14 (polar p9 pi09 (* 3.0 scale0))
               p18 (polar p21 0 (/ b 2.0))
         ) ;setq end
         (command "layer" "s" "rei" "")
         (command "line" p13 p14 "")
         (command "layer" "s" "pdim" "")
         (setq d1 (polar p24 pi27 (* 3 scale))
               d2 (polar d1 0 (* 50 factor))
               dp (polar d1 pi27 (* 10 scale))
         ) ;setq end
         (command "dim1" "hor" d1 d2 dp "")
         (setq d1 (Polar p21 pi09 (* 5 scale))
               d1 (polar d1 0 d)
               d2 (polar d1 0 b)
               d3 (polar d2 0 (* 75 factor))
               d4 (polar d3 0 t)
               dp (polar d1 pi09 (* 10 scale))
         ) ;setq end
         (command "dim" "hor" d1 d2 dp "" "con" d3 "" "con" d4 "" "e")
         (command "mirror" "c" p7 p29 "" p8 p0 "n")
;         
         (setq d1 (polar p7 pi27 (* 5.0 scale0))
               d2 (polar d1 0 (* 100 factor))
               dp (polar d1 pi27 (* 10 scale0))
               pdo (polar p13 pi27 (* 1.0 scale0))
               xd (* 5 scale0)
               rd (* 1 scale0)
         ) ;setq end
         (command "layer" "s" "pdim" "")
         (command "dim1" "hor" d1 d2 dp "")
         (command "layer" "s" "0" "")
         (command "donut" 0 rd pdo "")
         (command "array" "l" "" "r" 1 6 xd)
         (setq p1 (polar pdo 0 (* 15 scale0))
               p2 (polar p1 pi27 (* 15 scale0))
               pc (polar p2 pi27 (* 4 scale0))
               rr (* 4.0 scale0)
               htext (* 4 scale0)
         )
         (command "line" p1 p2 "")
         (command "circle" pc rr)
         (command "text" "j" "m" pc htext 0 "1")
         (setq p1 (polar p13 0 (* 0.7 L))
               p2 (polar p1 pi27 (* 15 scale0))
               pc (polar p2 pi27 (* 4 scale0))
         )
         (command "line" p1 p2 "")
         (command "circle" pc rr)
         (command "text" "j" "m" pc htext 0 "2")
         (setq p1 (polar p8 pi27 (* 15 scale0))
               p1 (polar p1 pi18 (/ d 2.0))
               p2 (polar p0 pi09 (* 5 scale0))
               p2 (polar p2 pi18 (/ d 2.0))
               pc1 (polar p1 pi27 (* 5 scale0))
               p3 (Polar p1 0 d)
               p4 (polar p2 0 d)
               pc2 (polar p3 pi27 (* 5 scale0))
               rr (* 5.0 scale0)
         )
         (command "linetype" "s" "axis" "")
         (command "layer" "s" "pdim" "")
         (command "line" p1 p2 "")
         (command "line" p3 p4 "")
         (command "linetype" "s" "bylayer" "")
         (command "circle" pc1 rr)
         (command "circle" pc2 rr)
         (command "layer" "s" "0" "")
) ;defun end
;--------
