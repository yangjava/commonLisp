(DEFUN C:BH(/ p0 olderr old txt r1)
 (setvar "cmdecho" 0)
 (setq olderr *error*
       *error* clmerr)
 (princ "\nCopyright (C) Y.F.Bao 画编号,打bh开始本命令.")
 (if (null scale) (setq scale (getreal "\n输入比例:")))
 (if (null R) (setq R (* 2.5 scale)))
 (if (null bh_ang) (setq bh_ang 0))
 (while (OR (NULL txt) (= txt ""))
   (princ "\n圆半径<")
   (princ R)
   (princ ">(,)\\字符角度<")
   (princ bh_ang)
   (princ ">(.)\\编号:")
   (setq txt (getstring))
 );while end
 (if (= txt ",")
   (progn
     (princ "\n输圆半径<")
     (princ (* 2.5 scale))
     (setq R (getdist ">:"))
     (if (null R) (setq R (* 2.5 scale)))
     (setq txt (getstring "\n编号:"))
   )
 )
 (if (= (substr txt 1 1) ".")
   (progn
     (if (= (strlen txt) 1)
       (progn
         (princ "\n输字符角度:")
         (setq old bh_ang)
         (setq bh_ang (getangle))
         (if (null bh_ang) (setq bh_ang old)
                           (setq bh_ang (/ (* bh_ang 180) PI))
         )
       );progn end
       (setq bh_ang (atof (substr txt 2)))
     );if end
     (setq txt (getstring "\n编号:"))
   )
 )
 (setq txt (strcase txt))
 (princ "\n圆心:")
 (setq r1 (/ r 400))
 (if (> (strlen txt) 0)
   (if (> (strlen txt) 1)
     (command "insert" "axi" "s" r1 "R" bh_ang pause  txt)
     (command "insert" "axi0" "s" r1 "R" bh_ang pause  txt)
   )
   (command "insert" "axi1"  pt  r1 "" "")
 )
 (setq *error* olderr)
 (setvar "cmdecho" 1)
)
