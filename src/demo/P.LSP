(defun c:p1()
 (setvar "cmdecho" 0)
 (setq p1 '(0 0)
       p2 (list '0 (/ (getvar "viewsize") 3))
 )
 (command "'pan" p1 p2)
 (setvar "cmdecho" 1)
 (princ)
)

(defun c:p2()
 (setvar "cmdecho" 0)
 (setq p1 '(0 0)
       p2 (list (* -1 (/ (getvar "viewsize") 5)) '0)
 )
 (command "'pan" p1 p2)
 (princ)
)

(defun c:p3()
 (setvar "cmdecho" 0)
 (setq p1 '(0 0)
       p2 (list (/ (getvar "viewsize") 5) '0)
 )
 (command "'pan" p1 p2)
 (princ)
)

(defun c:p4()
 (setvar "cmdecho" 0)
 (setq p1 '(0 0)
       p2 (list '0 (* -1 (/ (getvar "viewsize") 3)))
 )
 (command "'pan" p1 p2)
 (princ)
)

(defun c:p5()
  (setvar "cmdecho" 0)
  (command "zoom" "2x")
  (princ)
)

(defun c:p6()
  (setvar "cmdecho" 0)
  (command "zoom" "0.5x")
  (princ)
)

(defun c:p7()
  (setvar "cmdecho" 0)
  (command "zoom" "extents")
  (princ)
)
