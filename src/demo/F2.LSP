(defun c:f1()
        (setvar "cmdecho" 8)
        (princ "\n第一点:")
        (command "id" "end" pause)
        (setq p1 (getvar "lastpoint"))
        (princ "\n第二点:")
        (command "id" "nea" pause)
        (setq p2 (getvar "lastpoint") )
        (setq alfa (angle p1 p2)
              p3 (polar p2 (- alfa pi09) 900)
        )
        (command "line" p2 p3 "")
        (command "fillet" "r" 0)
        (command "fillet" p1 p3)
        (setvar "cmdecho" 1)
)
