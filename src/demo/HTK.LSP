(defun blch (/ x)
   (setvar "cmdecho" 0)
   (princ "\n输入图纸比例 1: <")
   (princ (fix bl))
   (setq x (getreal "> "))
   (if x (setq bl x blx (/ bl 100)))
   (setq d0 (* bl 10) d1 (* bl 15) d2 (* bl 43) d3 (* bl 47))
   (setq d4 (* bl 15) d5 (* bl 25) d6 (* bl 35) d7 (* bl 51) d8 (* bl 37))
   (setvar "USERR1" bl)
   (Setq scale bl)
   (setvar "ltscale" bl)
   (setdim 1.0)
   (if (null (tblsearch  "dimstyle" "Normal"))
       (command "dim1" "save" "Normal")
       (command "dim1" "save" "Normal" "N")
   ) ;if end
   (princ)
)

(defun drawline (/ ll lr ur ul ll0 lr0 ur0 ul0)
   (setvar "cmdecho" 0)
   (setq b1 (* b1 bl) b2 (* b2 bl) lw (* lw bl))
   (setq ll (list 0 0) lr (list (car p1) 0) ur p1 ul (list 0 (cadr p1)))
   (setq ll0 (list b1 b2) lr0 (list (- (car p1) b2) b2) ur0 (list (- (car p1) b2) (- (cadr p1) b2)) ul0 (list b1 (- (cadr p1) b2)))
   (command "limits" ll ur)
   (command "zoom" "a")
   (command "pline" ll "w" "0" "" lr ur ul "c")
   (command "pline" ll0 "w" lw "" lr0 ur0 ul0 "c")
   (command "layer" "m" "tk" "")
   (command "insert" "acad00" lr0 blx "" "0")
   (command "insert" "acad01" ul0 blx "" "0")
   (command "layer" "s" "0" "")
)
;
(defun C:TK (/ oer lw t1 t2 t3 t4 t5 t6 b1 b2 p1 a cd ths elv)
   (inivar) ;初始化系统变量
   (setq ths (getvar "thickness"))
   (setq elv (getvar "elevation"))
   (setq t1 1189.0 t2 841.0 t3 594.0 t4 419.0 t5 297.0 t6 209.0)
   (setq lw 0.5 b1 25.0 b2 10.0)
   (setq tzh1 (getvar "USERI1"))
   (setq tzh2 (getvar "USERI2"))
   (setq aaa1
        (strcat "A" (rtos tzh1 2 0))
   )
   (if (/= tzh2 0)
       (setq aaa1 (strcat aaa1 "+"))
   )
   (princ "\n输入图纸号<")
   (princ aaa1)
   (setq a (getstring ">:"))
   (if (eq a "") (setq a aaa1))
   (if (= (substr a 3 1) "+")
       (setvar "USERI2" 1)
       (setvar "USERI2" 0)
   )
   (blch)
   (setq t1 (* t1 bl) t2 (* t2 bl) t3 (* t3 bl) t4 (* t4 bl) t5 (* t5 bl) t6 (* t6 bl))
   (if (and (= (substr a 3 1) "+") (= (strlen a) 3)) (setq cd nil) (setq cd t))
   (setq a (atoi (substr a 2 1)))
   (setvar "USERI1" a)
   (if cd (progn
          (cond ((= a 0) (setq p1 (list t1 t2)))
                ((= a 1) (setq p1 (list t2 t3)))
                ((= a 2) (setq p1 (list t3 t4)))
                ((= a 3) (setq p1 (list t4 t5) b2 5.0))
                ((= a 4) (setq p1 (list t6 t5) b2 5.0))
          )
          )
       (progn
       (cond ((= a 1) (setq p1 (list t1 t3)))
             ((= a 2) (setq p1 (list t2 t4)))
             ((= a 3) (setq p1 (list t3 t5) b2 5.0))
             ((= a 4) (setq p1 (list t5 t5) b2 5.0))
      )
      )
   )
   (command "regen")
   (setvar "elevation" 0)
   (setvar "thickness" 0)
   (drawline)
   (setvar "elevation" elv)
   (setvar "thickness" ths)
   (resvar) ;还原系统变量
   (princ)
)
