(defun c:test (/ pt pts dis p1)
  (while (setq pt (getpoint "\nPoint: "))
    (if	(not p1)
      (setq p1 pt)
    )
    (setq pts (cons pt pts))
    (if (>= (length pts) 2)
     (grdraw pt p1 1))
    (setq p1 pt)
  )
  (setq dis 0.)
  (if pts
    (mapcar '(lambda (x y)
	       (setq dis (+ dis (distance x y)))
	     )
	    (reverse (cdr (reverse pts)))
	    (cdr pts)
    )
  )
  ;;(apply 'command (cons ".pline" pts))
  ;;(command)
  (if (not (zerop dis))
    (princ (strcat "\nDistance = " (rtos dis 2 4)))
  )
  (princ)
)
