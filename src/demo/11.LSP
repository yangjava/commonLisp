(defun C:myrectan (/ pt1 pt2 pt3 pt4)
  (setvar "cmdecho" 0)
  (graphscr)
  (setq pt1 (getpoint "\nFirst corner of the rectangle"))
  (setq pt3 (getpoint "\nsecond corner of the rectangle"))
  (setq pt2 (list (car pt1) (cadr pt3)))
  (setq pt4 (list (car pt3) (cadr pt1)))
  (command "line" pt1 pt2 pt3 pt4 "c")
  (alert "Your desired rectangle is sucessfully drawed")
  (prin1)
)
