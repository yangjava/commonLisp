(command "insert" "e:\\东方威尼斯\\jg-修改-40'\\wpj1.dwg"  pause  "" "" "")
(command "insert" "e:\\东方威尼斯\\jg-修改-40'\\wpj2.dwg"  pause  "" "" "")
(command "insert" "e:\\东方威尼斯\\jg-修改-40'\\wpj3.dwg"  pause  "" "" "")
(command "insert" "e:\\东方威尼斯\\jg-修改-40'\\wpj4.dwg"  pause  "" "" "")
(command "insert" "e:\\东方威尼斯\\jg-修改-40'\\wpj5.dwg"  pause  "" "" "")
(command "insert" "e:\\东方威尼斯\\jg-修改-40'\\wpj6.dwg"  pause  "" "" "")
(command "insert" "e:\\东方威尼斯\\jg-修改-40'\\wpj7.dwg"  pause  "" "" "")
(command "insert" "e:\\东方威尼斯\\jg-修改-40'\\wpj8.dwg"  pause  "" "" "")
(command "insert" "e:\\东方威尼斯\\jg-修改-40'\\wpj9.dwg"  pause  "" "" "")
(command "insert" "e:\\东方威尼斯\\jg-修改-40'\\wpj10.dwg"  pause  "" "" "")
(command "insert" "e:\\东方威尼斯\\jg-修改-40'\\wpj11.dwg"  pause  "" "" "")
(command "insert" "e:\\东方威尼斯\\jg-修改-40'\\wpj12.dwg"  pause  "" "" "")
(command "insert" "e:\\东方威尼斯\\jg-修改-40'\\wpj13.dwg"  pause  "" "" "")
(command "insert" "e:\\东方威尼斯\\jg-修改-40'\\wpj14.dwg"  pause  "" "" "")
(command "insert" "e:\\东方威尼斯\\jg-修改-40'\\wpj15.dwg"  pause  "" "" "")
(command "insert" "e:\\东方威尼斯\\jg-修改-40'\\wpj16.dwg"  pause  "" "" "")
(command "insert" "e:\\东方威尼斯\\jg-修改-40'\\wpj17.dwg"  pause  "" "" "")
(command "insert" "e:\\东方威尼斯\\jg-修改-40'\\wpj18.dwg"  pause  "" "" "")
(command "insert" "e:\\东方威尼斯\\jg-修改-40'\\wpj19.dwg"  pause  "" "" "")
(command "insert" "e:\\东方威尼斯\\jg-修改-40'\\wpj20.dwg"  pause  "" "" "")
(command "insert" "e:\\东方威尼斯\\jg-修改-40'\\wpj21.dwg"  pause  "" "" "")
(command "insert" "e:\\东方威尼斯\\jg-修改-40'\\wpj22.dwg"  pause  "" "" "")
(command "insert" "e:\\东方威尼斯\\jg-修改-40'\\wpj23.dwg"  pause  "" "" "")
(command "insert" "e:\\东方威尼斯\\jg-修改-40'\\wpj24.dwg"  pause  "" "" "")
(command "insert" "e:\\东方威尼斯\\jg-修改-40'\\wpj25.dwg"  pause  "" "" "")
(command "insert" "e:\\东方威尼斯\\jg-修改-40'\\wpj26.dwg"  pause  "" "" "")
