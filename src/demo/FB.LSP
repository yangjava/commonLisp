(defun c:fb()
 ;计算筏板底板配筋
 (setvar "cmdecho" 0)
  (textscr)
  (setq p0 (getreal "\np0(KN/m2):")
        lx (getreal "lx(m):")
        ly (getreal "ly(m):")
        ramda (/ ly lx)
        txt (strcat "ramda=" (rtos ramda 2 3))
   ) ;setq end
   (princ txt)
   (setq fx (getreal "\nfx:")
         fy (getreal "fy:")
         xx (getreal "xx:")
         yn (getstring "边跨(1)/中间跨(0):<0>")
	 b (getreal "基础梁宽(m):")
         h (getreal "底板厚(m):")
   	 h0 (- h 0.035)
         yn (if (= yn "") "0" yn)
         plx (* p0 lx lx)
         ply (* p0 ly ly)
         Mx (* fx plx)
         My (* fy ply)
         dMx (* 0.25 xx p0 lx b)
	 dMy (- 1 xx)
         dmy (* 0.25 dMy p0 ly b)
    ) ;setq end
    (if (= yn "1")
        (setq xx1 (getreal "第二跨xx:")
              aa1 (/ xx 16)
              aa2 (/ xx1 24)
              aa1 (+ aa1 aa2)
              M0x (* aa1 plx)
	      M0x (- M0x dMx)
              aa1 (/ (- 1 xx) 16)
  	      aa2 (/ (- 1 xx1) 24)
	      aa1 (+ aa1 aa2)
	      M0y (* aa1 ply)	
              M0y (- M0y dMy)
        ) ;setq end
        (setq M0x (* xx plx (/ 1 12.0))
              M0y (* (- 1 xx) ply (/ 1 12.0))
              M0x (- M0x dMx)
	      M0y (- M0y dMy)
        ) ;setq end
     ) ;if end
     (setq fac (* 0.9 310 h0 0.001)
           asx (/ Mx fac)
           asy (/ My fac)
 	   as0x (/ M0x fac)
	   as0y (/ M0y fac)
           txt1 (strcat "Mx= " (rtos Mx 2 2) " (KN/m2)  ASx= " (rtos asx 2 2))
           txt2 (strcat "\nMy= " (rtos My 2 2) " (KN/m2)  ASy= " (rtos asy 2 2))
           txt3 (strcat "\nM0x=" (rtos M0x 2 2) " (KN/m2)  AS0x= " (rtos as0x 2 2))
           txt4 (strcat "\nM0y=" (rtos M0y 2 2) " (KN/m2)  AS0y= " (rtos as0y 2 2))
    ) ;setq end
    (princ txt1)
    (princ txt2)
    (princ txt3)
    (princ txt4)
    (princ)
) ;defun end
