;+-------------------------------+
;+ 计算TAT的42种内力组合         +
;+ 文件名: NL.lsp                +
;+-------------------------------+
;将实数ss转换成指定长度n的字符串
(defun rs(ss n / ll ll1 ind)
  (setq ss (rtos ss 2 2)
        ll (strlen ss)
        ll1 (- n ll)
        ind 0
  ) ;setq end
  (while (< ind ll1)
     (setq ss (strcat " " ss)
           ind (1+ ind)
     ) ;setq end
  ) ;while end
  (setq ss ss)
) ;dedun end

; 计算TAT
(defun c:nlzh()
  (inivar) ;初始化系统变量
  (textscr)
  (setq l-lll (list ;组合系数
   '( 1 0.0  0.0  0.0   0.0  1.2 1.4)
   '( 2 0.0  0.0  0.0   0.0  1.0 1.4)
   '( 3 0.0  0.0  1.4   0.0  1.2 0.0)
   '( 4 0.0  0.0  -1.4  0.0  1.2 0.0)
   '( 5 0.0  0.0  0.0   1.4  1.2 0.0)
   '( 6 0.0  0.0  0.0  -1.4  1.2 0.0)
   '( 7 0.0  0.0  1.4   0.0  1.0 0.0)
   '( 8 0.0  0.0  -1.4  0.0  1.0 0.0)
   '( 9 0.0  0.0  0.0   1.4  1.0 0.0)
   '(10 0.0  0.0  0.0  -1.4  1.0 0.0)
   '(11 0.0  0.0  1.19  0.0  1.2 1.19)
   '(12 0.0  0.0  -1.19 0.0  1.2 1.19)
   '(13 0.0  0.0  0.0   1.19 1.2 1.19)
   '(14 0.0  0.0  0.0  -1.19 1.2 1.19)
   '(15 0.0  0.0  1.19   0.0 1.0 1.19)
   '(16 0.0  0.0 -1.19   0.0 1.0 1.19)
   '(17 0.0  0.0  0.0   1.19 1.0 1.19)
   '(18 0.0  0.0  0.0  -1.19 1.0 1.19)
   '(19 1.3  0.0  0.0    0.0 1.2 0.6)
   '(20 -1.3 0.0  0.0    0.0 1.2 0.6)
   '(21 0.0  1.3  0.0    0.0 1.2 0.6)
   '(22 0.0  -1.3 0.0    0.0 1.2 0.6)
   '(23 1.3  0.0  0.0    0.0 1.0 0.5)
   '(24 -1.3 0.0  0.0    0.0 1.0 0.5)
   '(25 0.0  1.3  0.0    0.0 1.0 0.5)
   '(26 0.0 -1.3  0.0    0.0 1.0 0.5)
   '(27 1.3  0.0  0.0   0.28 1.0 0.6)
   '(28 1.3  0.0  0.0  -0.28 1.2 0.6)
   '(29 -1.3 0.0  0.0   0.28 1.2 0.6)
   '(30 -1.3 0.0  0.0  -0.28 1.2 0.6)
   '(31 0.0  1.3  0.28   0.0 1.2 0.6)
   '(32 0.0  1.3 -0.28   0.0 1.2 0.6)
   '(33 0.0 -1.3  0.28   0.0 1.2 0.6)
   '(34 0.0 -1.3 -0.28   0.0 1.2 0.6)
   '(35 1.3  0.0   0.0  0.28 1.0 0.5)
   '(36 1.3  0.0   0.0 -0.28 1.0 0.5)
   '(37 -1.3 0.0   0.0  0.28 1.0 0.5)
   '(38 -1.3 0.0   0.0 -0.28 1.0 0.5)
   '(39 0.0  1.3  0.28   0.0 1.0 0.5)
   '(40 0.0  1.3 -0.28   0.0 1.0 0.5)
   '(41 0.0 -1.3  0.28   0.0 1.0 0.5)
   '(42 0.0 -1.3 -0.28   0.0 1.0 0.5)
  ))
  (load "tab.lsp")
  (princ "\nE-x,E-y ---- x,y方向地震效应")
  (princ "\nW-x,W-y ---- x,y方向风荷载效应")
  (princ "\nV-D,V-L ---- 垂直静,活荷载效应")
 (princ "\输入六组内力标准值E-x,E-y,W-x,W-y,V-D,V-L:")
 (princ "\n")
 (setq scale 1
       l-l (readlh)
       fname (getstring "\n输入结果文件名(不用输入路径和扩展名):")
       fname (strcat (getvar "DWGPREFIX") fname ".txt")
       index 1
       f (open fname "w")
       txt1 "  NO       E-X       E-Y       W-X       W-Y       V-D       V-L  内力组合"
       t1 (nth 0 l-l)
       t2 (nth 1 l-l)
       t3 (nth 2 l-l)
       t4 (nth 3 l-l)
       t5 (nth 4 l-l)
       t6 (nth 5 l-l)
       txt2 (strcat "    " (rs t1 10) (rs t2 10) (rs t3 10) (rs t4 10) (rs t5 10) (rs t6 10))
  ) ;setq end
  (write-line txt1 f)
  (write-line txt2 f)
  (while (<= index 42)
   (Setq l-l1 (cdr (assoc index l-lll))
         l1 (nth 0 l-l1)
         l2 (nth 1 l-l1)
         l3 (nth 2 l-l1)
         l4 (nth 3 l-l1)
         l5 (nth 4 l-l1)
         l6 (nth 5 l-l1)
 	 res (+ (* t1 l1) (* t2 l2) (* t3 l3) (* t4 l4) (* t5 l5) (* t6 l6))    
         txt3 (strcat (rs index 4) (rs l1 10) (rs l2 10) (rs l3 10) (rs l4 10) (rs l5 10) (rs l6 10) (rs res 10))
         index (1+ index)
   )setq end
   (write-line txt3 f)
  ) ;while end
 (close f)
 (princ (strcat "\n计算完成，结果存在" fname "中"))
 (resvar) ;还原系统变量
 (princ)
) ;defun end
