(defun C:chw(/ ss txsize n index ent type oldsize newsize ent1)
 (setq ss (ssget))
 (setq txsize (getdist "\n输入新的长宽比:"))
 (setq n (sslength ss))
 (setq index 0)
 (setvar "cmdecho" 0)
 (repeat n
  (setq ent (entget (ssname ss index)))
  (setq index (+ 1 index))
  (setq ty (assoc 0 ent))
  (if (= "TEXT" (cdr ty))
   (progn
    (setq oldsize (assoc 41 ent))
    (setq newsize (cons (car oldsize) txsize))
    (setq ent1 (subst newsize oldsize ent))
    (entmod ent1)
   )
  )
 )
 (setvar "cmdecho" 1)
)
