(defun C:key1()   ;define hot key
  (textscr)
  (prompt "\e[0;72;'p1';13p")
  (prompt "\e[0;75;'p2';13p")
  (prompt "\e[0;77;'p3';13p")
  (prompt "\e[0;80;'p4';13p")
  (prompt "\e[224;72;'p1';13p")
  (prompt "\e[224;75;'p2';13p")
  (prompt "\e[224;77;'p3';13p")
  (prompt "\e[224;80;'p4';13p")
  (princ)
  (graphscr)
  (princ)
)
