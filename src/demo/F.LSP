(defun ss(at)
 (setq res (* at at))
) ;defun end

(setq l-l (list
  '(20   1     1.0000     338.48     1.0000     594.38     1.0000     269.09)
  '(19   1     0.9456     320.07     0.7958     473.01     0.6634     178.52)
  '(18   1     0.8900     301.25     0.5814     345.58     0.2955      79.53)
  '(17   1     0.8332     282.03     0.3617     214.99    -0.0718     -19.32)
  '(16   1     0.7754     262.45     0.1426      84.77    -0.4027    -108.36)
  '(15   1     0.7166     242.54    -0.0693     -41.18    -0.6632    -178.46)
  '(14   1     0.6568     218.32    -0.2686    -156.79    -0.8276    -218.69)
  '(13   1     0.5960     198.09    -0.4515    -263.54    -0.8741    -230.97)
  '(12   1     0.5351     177.86    -0.6039    -352.50    -0.7884    -208.33)
  '(11   1     0.4750     162.77    -0.7186    -432.36    -0.5895    -160.58)
  '(10   1     0.4172     142.95    -0.7926    -476.88    -0.3316     -90.32)
  '( 9   1     0.3608     123.64    -0.8311    -500.06    -0.0317      -8.64)
  '( 8   1     0.3065     105.02    -0.8340    -501.79     0.2755      75.06)
  '( 7   1     0.2548      89.36    -0.8026    -494.24     0.5540     154.46)
  '( 6   1     0.2065      72.42    -0.7422    -457.06     0.7689     214.37)
  '( 5   1     0.1618      56.73    -0.6574    -404.83     0.9040     252.05)
  '( 4   1     0.1212      42.50    -0.5535    -340.83     0.9457     263.65)
  '( 3   1     0.0853      30.61    -0.4357    -274.47     0.8895     253.70)
  '( 2   1     0.0644      35.41    -0.3571    -344.73     0.8050     351.81)
  '( 1   1     0.0258      15.08    -0.1732    -177.54     0.4588     212.91)
  )
  l-l1 (list
  '(20   1    -1.0000    -145.67     0.8744      69.33    -0.8116     -45.68)
  '(19   1    -0.5125     -74.65     0.2904      23.02    -0.0797      -4.49)
  '(18   1     0.0253       3.69    -0.3316     -26.29     0.6150      34.62)
  '(17   1     0.5125      74.65    -0.7800     -61.84     0.8855      49.84)
  '(16   1     0.8501     123.83    -0.8955     -71.00     0.5811      32.71)
  '(15   1     0.9689     141.14    -0.6407     -50.80    -0.1048      -5.90)
  '(14   1     0.8403     120.21    -0.1008      -7.85    -0.7634     -42.19)
  '(13   1     0.4606      65.89     0.5645      43.95    -1.0000     -55.27)
  '(12   1    -0.0525      -7.51     1.0000      77.86    -0.4633     -25.61)
  '(11   1    -0.5404     -79.69     0.9843      79.00     0.3033      17.28)
  '(10   1    -0.8439    -124.45     0.5868      47.10     0.7110      40.51)
  '( 9   1    -0.9629    -142.00    -0.0116      -0.93     0.7048      40.16)
  '( 8   1    -0.8729    -128.72    -0.5860     -47.04     0.3443      19.62)
  '( 7   1    -0.5925     -89.42    -0.9276     -76.19    -0.1632      -9.52)
  '( 6   1    -0.1918     -28.95    -0.9187     -75.46    -0.5560     -32.42)
  '( 5   1     0.2502      37.76    -0.5806     -47.69    -0.6729     -39.24)
  '( 4   1     0.6423      96.94    -0.0298      -2.45    -0.4548     -26.52)
  '( 3   1     0.9034     139.48     0.5476      46.02     0.0178       1.06)
  '( 2   1     0.9565     226.30     0.7926     102.05     0.3300      30.17)
  '( 1   1     0.6642     166.86     0.7562     103.40     0.7380      71.64)
   )
 )
 (setq ind 1 sum1 0 sum2 0 sum3 0 sum4 0 sum5 0 sum6 0 
       zj1 0 zj2 0 zj3 0 zj4 0 zj5 0 zj6 0)
 (while (<= ind 20)
	(setq l123 (cdr (assoc ind l-l))
	      l456 (cdr (assoc ind l-l1))
	      f1 (nth 2 l123)
	      f2 (nth 4 l123)
	      f3 (nth 6 l123)
	      f4 (nth 2 l456)
	      f5 (nth 4 l456)
	      f6 (nth 6 l456)

	      d1 (nth 1 l123)
	      d2 (nth 3 l123)
	      d3 (nth 5 l123)
	      d4 (nth 1 l456)
	      d5 (nth 3 l456)
	      d6 (nth 5 l456)
	   	
	      sum1 (+ sum1 f1)
	      sum2 (+ sum2 f2)
	      sum3 (+ sum3 f3)
	      sum4 (+ sum4 f4)
	      sum5 (+ sum5 f5)
	      sum6 (+ sum6 f6)
		zj1 (+ zj1 (* d1 d3))
		zj2 (+ zj2 (* d2 d3))
		zj3 (+ zj3 (* d3 d4))
		zj4 (+ zj4 (* d3 d5))
		zj5 (+ zj5 (* d3 d6))

	      ind (1+ ind)
	) ;set end
  ) ;while end
 (setq txt1 (strcat "\nQ01=" (rtos sum1 2 4)))
 (princ txt1)
 (setq txt1 (strcat "\nQ02=" (rtos sum2 2 4)))
 (princ txt1)
 (setq txt1 (strcat "\nQ03=" (rtos sum3 2 4)))
 (princ txt1)
 (setq txt1 (strcat "\nQ04=" (rtos sum4 2 4)))
 (princ txt1)
 (setq txt1 (strcat "\nQ05=" (rtos sum5 2 4)))
 (princ txt1)
 (setq txt1 (strcat "\nQ06=" (rtos sum6 2 4)))
 (princ txt1)
 (Setq sum (+ (ss sum1) (ss sum2) (ss sum3) (ss sum4) (ss sum5) (ss sum6))
       sum (sqrt sum))
 (setq txt1 (strcat "\nQ0=" (rtos sum 2 4)))
 (princ txt1)
 (setq txt1 (strcat "\nd1*d2=" (rtos zj1 2 4)))
 (princ txt1)
 (setq txt1 (strcat "\nd1*d3=" (rtos zj2 2 4)))
 (princ txt1)
 (setq txt1 (strcat "\nd1*d4=" (rtos zj3 2 4)))
 (princ txt1)
 (setq txt1 (strcat "\nd1*d5=" (rtos zj4 2 4)))
 (princ txt1)
 (setq txt1 (strcat "\nd1*d6=" (rtos zj5 2 4)))
 (princ txt1)


;    -----------------------------------------------------------------------
(princ "\n   Qox =     4896.360 (kN)     Qox/Ge =   2.81%")
(princ)
;    Mox =   160175.516 (kN-m)
