(defun C:chDIM(/ ss txsize n index ent ty oldsize newsize ent1)
 (setq ss (ssget))
 (setq txsize (getSTRING "\n:new dim stlye:"))
 (setq n (sslength ss))
 (setq index 0)
; (setvar "cmdecho" 0)
 (repeat n
  (setq ent (entget (ssname ss index)))
  (setq index (+ 1 index))
  (setq ty (assoc 0 ent))
  (if (= "DIMENSION" (cdr ty))
   (progn
    (setq oldsize (assoc 3 ent))
    (setq newsize (cons (car oldsize) txsize))
    (setq ent1 (subst newsize oldsize ent))
    (entmod ent1)
   )
  )
 )
 (setvar "cmdecho" 1)
)
