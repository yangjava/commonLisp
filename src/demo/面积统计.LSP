((defun c:xdtb_ptarea (/ pt pts area e)
  (while (setq pt (getpoint "\nPoint: "))
    (if	(= (type pt) 'LIST)
      (setq pts (cons pt pts))
    )
  )
  (if pts
    (progn
      (xdrx_begin)
      (xdrx_sysvar_push "osmode" "dimzin")
      (setvar "dimzin" 0)
      (setq area (abs (apply 'xdrx_parea pts)))
      (setq e (xdrx_entsel "\n拾取标注文字: " '((0 . "text"))))
      (xdrx_setenttodb (car e))
      (xdrx_setxdata "area" (rtos area 2 1))
      (princ (strcat "\nArea = " (rtos area 2 1)))
      (xdrx_sysvar_pop)
      (xdrx_end)
    )
  )
  (princ)
)
(defun c:xdtb_tjarea (/ e ss lay str area pt)
  (setq e (xdrx_entsel "\n拾取典型文字: " '((-3 ("AREA")))))
  (if e
    (progn
      (xdrx_begin)
      (xdrx_sysvar_push "osmode")
      (setvar "osmode" 0)
      (xdrx_setenttodb (car e))
      (setq lay (xdrx_getentdxf 8))
      (princ "\n拾取统计范围(回车全选)...")
      (if (not (setq ss (ssget (list (cons 8 lay) '(-3 ("area"))))))
	(setq ss
	       (ssget "x" (list (cons 8 lay) '(-3 ("area"))))
	)
      )
      (if ss
	(progn
	  (setq pt (getpoint "\n输出点: "))
	  (xdrx_setsstodb ss 0)
	  (while (setq e1 (xdrx_getentdata 0))
	    (setq str  (xdrx_getentdxf 1)
		  area (car (xdrx_getxdata e1 "area"))
	    )
	    (vl-cmdf ".text" pt 1.6 "0" (strcat str "    " area))
	    (setq pt (polar pt (- _pi2) 6.))
	  )
	)
      )
      (xdrx_sysvar_pop)
      (xdrx_end)
      (princ)
    )
  )
)
