(defun C:myrectan (/ pt1 pt2 pt3 pt4)
  (setvar "cmdecho" 0)
  (graphscr)
  (setq fi (getstring "\nEnter file name:"))
  (setq f (open fi "a"))
  (setq pt1 (getpoint "\nFirst corner of the rectangle"))
  (princ pt1 f)
  (setq pt3 (getpoint "\nsecond corner of the rectangle"))
  (princ pt3 f)
  (setq pt2 (list (car pt1) (cadr pt3)))
  (setq pt4 (list (car pt3) (cadr pt1)))
  (command "line" pt1 pt2 pt3 pt4 "c")
  (alert "Your desired rectangle is sucessfully drawed")
  (prin1)
) 
(defun C:remember()
      (setq fi (getstring "\nEnter file name:"))
      (setq f (open fi "a"))
      (prompt "Now draw 4 points of a rectangel:")
      (setq p1 (getpoint "nFirst point:"))
      (princ p1 f)
      (set p2 (getpoint "nSecond point:"))
      (princ p2 f)
      (setq p3 (getpoint "\nThird point:"))
      (princ p3 f)
      (setq p4 (getpoint "\nFouth point:"))
      (princ p4 f)
      (close f)
      (command "line" p1 p2 p3 p4 "c")
     )
