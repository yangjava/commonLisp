(VMON)
;
(setq factor 1)
(command "layer" "m" "pdim" "c" "green" "" "")
(command "layer" "m" "rei" "c" "1" "" "s" "0" "")
;
(defun jc2_dash(p_dash b_dash)
 (setq p_p1 (polar p_dash pi18 (+ (/ b 2) (* 2 scale)))
       delta (/ b_dash 3.0)
       p_p2 (polar p_p1 0 (+ (* 2 scale) delta))
       p_p3 (polar p_p2 0 (/ delta 2.0))
       p_p3 (polar p_p3 (* pi09 0.5) (* 6 scale))
       p_p5 (polar p_p2 0 delta)
       p_p4 (polar p_p5 pi18 (/ delta 2.0))
       p_p4 (polar p_p4 (* pi09 -1.5) (* 6 scale))
       p_p6 (polar p_p5 0 (+ delta (* 2 scale)))
 ) ;setq end
 (command "line" p_p1 p_p2 p_p3 p_p4 p_p5 p_p6 "")
) ;defun end
;
(defun clmerr(s)
   (if (/= s "Function cancelled")
       (princ (strcat "\nError:" s))
   )
   (command)
   (command "layer" "s" "0" "")
   (setvar "blipmode" 1)
   (setvar "cmdecho" 1)
   (setvar "osmode" 0)
   (setvar "dimlfac" 1.0)
   (setvar "cmdecho" 1)
   (setq *error* oer)
   (princ)
)
;
(defun intp(ntype p0 p1 R)
 (if (< (distance p0 p1) R)
     (progn
          (setq xx0 (nth 0 p0)
                yy0 (nth 1 p0)
                x  (nth 0 p1)
                y  (nth 1 p1)
                RR (* R R)
                ydd (* (- y yy0) (- y yy0))
                xdd (* (- x xx0) (- x xx0))
                xd (sqrt (- RR ydd))          
                yd (sqrt (- RR xdd))
          ) ;setq end
          ;-----------
          ;(princ "\np0:") (princ x) (princ " , ") (princ y)
          ;---------
          (setq x (if (= ntype 1) (+ xx0 xd) x)
                y (if (= ntype 2) (+ yy0 yd) y)
          )      
          ;-----------
          ;(princ "\np:") (princ x) (princ " , ") (princ y)
          ;-----------
          (setq p (list x y)
          ) ;setq end
     ) ;progn end
     (setq p p1)
 ) ;if end
) ;defun end
;
;(setq p0 (getpoint "\p0"))
(defun pim(p0)
       (command "layer" "s" "0" "")
       (setq AA2 (/ AA 2.0)
             BB2 (/ BB 2.0)
             p41 (polar p0 pi18 BB2)
             p41 (polar p41 pi27 AA2)
             p42 (polar p41 0 BB)
             p43 (polar p42 pi09 AA)
             p44 (polar p41 pi09 AA)
             R (if (> AA2 BB2) BB2 AA2)
             R (* 0.7 R)
       ) ;setq end    
       (command "line" p41 p42 p43 p44 "c")
; draw arc       
       (setq p1 (polar p41 0 R)
             p2 (polar p41 pi09 R)
       )
       (command "arc" "c" p41 p1 p2)
;draw collumn
       (setq AA2 (/ h 2.0)
             BB2 (/ b 2.0)
             p31 (polar p0 pi18 BB2)
             p31 (polar p31 pi27 AA2)
             p32 (polar p31 0 b)
             p33 (polar p32 pi09 h)
             p34 (polar p31 pi09 h)
        ) ;setq end
       (command "line" p31 p32 p33 p34 "c")
       (setq AA2 (+ (/ h 2.0) (* 2 scale))
             BB2 (+ (/ b 2.0) (* 2 scale))
             p31 (polar p0 pi18 BB2)
             p31 (polar p31 pi27 AA2)
             p32 (polar p31 0 (* BB2 2.0))
             p33 (polar p32 pi09 (* 2.0 AA2))
             p34 (polar p31 pi09 (* 2.0 AA2))
        ) ;setq end
       (command "line" p31 p32 p33 p34 "c")
       (command "line" p42 p32 "")
       (command "line" p43 p33 "")
       (command "line" p44 p34 "")
       (setq ang (angle p41 p31)
             pp (polar p41 ang R)
       ) ;setq end
       (command "line" pp p31 "")
; draw reinforcement       
       (command "layer" "s" "rei" "")
       (setq scale0 (getvar "userr1")
             dx (* 1 scale0)
             dy dx
             x41 (nth 0 p41)
             y41 (nth 1 p41)
             xr0 (+ x41 dx)
             yr0 (+ y41 dy)
             n (fix (/ (- R dx) (* 5 scale0)))
             index 0
        ) ;setq end     
        (repeat (1+ n)
            (setq dx (* index (* 5 scale0))
                  dy dx
                  index (1+ index)
                  x1 (+ xr0 dx)
                  y1 (+ yr0 dy)
                  po1 (list x1 yr0)
                  po2 (intp 2 p41 po1 R)
                  po3 (list xr0 y1)
                  po4 (intp 1 p41 po3 R)
            ) ;setq end
            (command "line" po1 po2 "")
            ;-------
            ;(princ "\n draw rei line")
            ;(princ index) (getstring "\npress any key to continue")
            ;------
            (command "line" po3 po4 "")
        ) ;repeat end
;draw rei num1
        (command "layer" "s" "0" "")
        (setq dx (* 2.5 scale0)
              dy dx
              pr0 (list xr0 yr0)
              p1 (polar pr0 0 dx)
              p1 (polar p1 pi27 (* 10 scale0))
              p2 (polar po3 0 dx)
              p2 (polar p2 pi09 (* 2 scale0))
              p3 (polar p1 pi18 (* 20 scale0))
              pc (polar p3 pi18 (* 4 scale0))
              pr (* 4 scale0)
              htext (* 4 scale0)
         ) ;setq end
         (command "line" p2 p1 p3 "")
         (command "circle" pc pr)
         (command "text" "j" "m" pc htext 0 "2")
;draw rei num2
        (setq dx (* 2.5 scale0)
              dy dx
              pr0 (list xr0 yr0)
              p1 (polar pr0 pi09 dy)
              p1 (polar p1 pi18 (* 10 scale0))
              p2 (polar po1 90 dx)
              p2 (polar p2 0 (* 2 scale0))
              p3 (polar p1 pi09 (* 20 scale0))
              pc (polar p3 pi09 (* 4 scale0))
         ) ;setq end
         (command "line" p2 p1 p3 "")
         (command "circle" pc pr)
         (command "text" "j" "m" pc htext 90 "1")
;draw axis
         (setq AA2 (/ AA 2.0)
               BB2 (/ BB 2.0)
               p1 (polar p0 0 (+ BB2 (* 5 scale0)))
               p2 (polar p0 pi18 (+ BB2 (* 40 scale0)))
               p3 (polar p0 pi27 (+ AA2 (* 35 scale0)))
               p4 (polar p0 pi09 (+ AA2 (* 5 scale0)))
               rr (* 5 scale0)
               pc1 (polar p2 pi18 rr)  
               pc2 (polar p3 pi27 rr)
          ) ;setq end
          (command "layer" "s" "pdim" "")
          (command "line" p1 p2 "")
          (command "change" "l" "" "p" "lt" "axis" "")
          (command "line" p3 p4 "")
          (command "change" "l" "" "p" "lt" "axis" "")
          (command "circle" pc1 rr)          
          (command "circle" pc2 rr)
;draw dimension
         (command "layer" "s" "pdim" "")
         (setvar "dimdli" 0)
         ;(princ "\ndim1")
         (setq d1 (polar p41 pi18 (* 25 scale))         
               d2 (polar d1 pi09 (/ AA 2.0))
               d3 (polar d2 pi09 (/ AA 2.0))
               dp (polar d3 pi18 (* 10 scale))
         ) ;setq end
         (command "dim" "ver" d1 d2 dp "" "con" d3 "" "e")
         (setq dp d2
               d2 (polar d2 0 (* 10 scale))
               d1 (polar d2 pi27 (/ h 2.0))
               d3 (polar d2 pi09 (/ h 2.0))
         ) ;setq end
         (command "dim" "ver" d1 d2 dp "" "con" d3 "" "e")
        ;dim2
         (setq d1 (polar p41 pi27 (* 20 scale))         
               d2 (polar d1 0 (/ BB 2.0))
               d3 (polar d2 0 (/ BB 2.0))
               dp (polar d3 pi27 (* 10 scale))
         ) ;setq end
         (command "dim" "hor" d1 d2 dp "" "con" d3 "" "e")
         (setq dp d2
               d2 (polar d2 pi09 (* 10 scale))
               d1 (polar d2 pi18 (/ b 2.0))
               d3 (polar d2 0 (/ b 2.0))
         ) ;setq end                  
         (command "dim" "hor" d1 d2 dp "" "con" d3 "" "e")
   (command "layer" "s" "0" "")
) ;defun end
;      
(defun  pom(p0)
       (jc2_dash p0 b)
       (setq x0 (nth 0 p0)
             y0 (nth 1 p0)
             pi09 (* pi 0.5)
             pi18 pi
             pi27 (* pi 1.5)
             scale0 (getvar "userr1")
        ) ;setq end
        (setq p1 (polar p0 pi18 (/ b 2.0))
              p2 (polar p1 pi27 (* 40 scale0))              
              p3 (Polar p2 pi18 (* 2 scale0))
              p4 (polar p0 pi27 (+ (* 40 scale) h2))
              p4 (polar p4 pi18 (/ BB 2.0))
              p5 (polar p4 pi27 h1)
              p6 (polar p5 pi18 (* 100 factor))
              p7 (polar p6 pi27 (* 100 factor))
              p8 (polar p7 0 (+ (* 100 factor) (/ BB 2.0)))
              p9 (polar p6 0 (+ (* 100 factor) (/ BB 2.0))) 
        ) ;setq end
        (setvar "dimdli" 0)
        (command "layer" "s" "0" "")
        (command "line" p1 p2 p3 p4 p5 "")
        (command "line" p8 p7 p6 p9 "")
        (command "layer" "s" "pdim" "")
        (setq d1 (polar p7 pi18 (* 3 scale0))
              d2 (polar d1 pi09 (* 100 factor))
              d3 (polar d2 pi09 h1)
              d4 (polar d3 pi09 h2)
              d5 (polar d4 pi09 (* 20 scale0))
              dp (polar d1 pi18 (* 10 scale0))
         )
         (command "dim" "ver" d1 d2 dp "" "con" d3 "" "con" d4 "" "con" d5 "40d" "e")
         (setq d1 (polar p2 pi09 (* 5 scale))
               d2 (polar d1 pi18 (* 2 scale))
               dp (polar d1 pi09 (* 10 scale))
         ) ;setq end
         (command "dim1" "hor" d1 d2 dp "50")
         (setq p_bg (polar p6 pi18 (* 25 scale0))
               sc_x (/ scale0 100.0)
               sc_y sc_x
         )
         (command "insert" "elul" p_bg sc_x sc_y 0 bg)
         (setq p13 (polar p5 0 (* 2.0 scale0))
               p13 (polar p13 pi09 (* 3.0 scale0))
               p14 (polar p9 pi09 (* 3.0 scale0))
               p15 (polar p1 pi27 (* 20 scale0))
               p15 (polar p15 0 (* 1.5 scale0))
               p16 (polar p14 pi09 (* 1.5 scale0))
               a1 (/ b 2.0)
               p16 (polar p16 pi18 (- a1 (* 1.5 scale0)))
               p17 (polar p16 pi18 (* 10 scale0))
               p18 (polar p15 0 (- a1 (* 1.5 scale0)))
               p19 (polar p15 (* pi09 -0.5) (* 2 scale0))
               p20 (polar p19 pi09 (* 10 scale0))
               p21 (polar p20 0 (+ (* a1 2) (* 20 scale0)))
               txt_1 "基础插筋"
               txt_2 "规格同柱主筋"
               h_txt (* 4 scale0)
               p1_txt (polar p20 0 (+ (* a1 2) (* 4 scale0)))
               p2_txt (polar p1_txt pi27 (* 6 scale0))
               p1_txt (polar p1_txt pi09 (* 2 scale0))
         ) ;setq end
         (command "layer" "s" "rei" "")
         (command "line" p13 p14 "")
         (command "line" p15 p16 p17 "") 
         ;(command "line" p14 p18 "")
;         
         (command "line" p15 p19 "")
         (command "layer" "s" "0" "")
         (command "line" p19 p20 p21 "")
         (command "mirror" "c" p7 p18 "" p8 p18 "n")
         (command "text" p1_txt h_txt 0 txt_1) 
         (command "text" p2_txt h_txt 0 txt_2)
;         
         (setq d1 (polar p7 pi27 (* 5.0 scale0))
               d2 (polar d1 0 (* 100 factor))
               dp (polar d1 pi27 (* 10 scale0))
               pdo (polar p13 pi27 (* 1.0 scale0))
               xd (* 5 scale0)
               rd (* 1 scale0)
         ) ;setq end
         (command "layer" "s" "pdim" "")
         (command "dim1" "hor" d1 d2 dp "")
         (command "layer" "s" "0" "")
         (command "donut" 0 rd pdo "")
         (command "array" "l" "" "r" 1 6 xd)
         (setq p1 (polar pdo 0 (* 15 scale0))
               p2 (polar p1 pi27 (* 15 scale0))
               pc (polar p2 pi27 (* 4 scale0))
               rr (* 4.0 scale0)
               htext (* 4 scale0)
         )
         (command "line" p1 p2 "")
         (command "circle" pc rr)
         (command "text" "j" "m" pc htext 0 "1")
         (setq p1 (polar p13 0 (* 0.7 BB))
               p2 (polar p1 pi27 (* 15 scale0))
               pc (polar p2 pi27 (* 4 scale0))
         )
         (command "line" p1 p2 "")
         (command "circle" pc rr)
         (command "text" "j" "m" pc htext 0 "2")
         (setq p1 (polar p8 pi27 (* 15 scale0))
               p2 (polar p0 pi09 (* 5 scale0))
               pc (polar p1 pi27 (* 5 scale0))
               rr (* 5.0 scale0)
         )
         (command "line" p1 p2 "")
         (command "circle" pc rr)
         (command "layer" "s" "0" "")
) ;defun end
;--------
;
(defun C:JC2()
 (setvar "cmdecho" 0)
 (setvar "dimlfac" (/ 1.0 factor))
 (setq oer *error* *error* clmerr)
 (setq scale0 (getvar "userr1"))
 (command "layer" "s" "0" "")
      (setq scale0 (getvar "userr1"))
      (setq l1 (+ BB (* 30 scale))      
            l2 (+ h1 h2 AA (* 100 scale))
      ) ;setq end
      (princ "\n基础插入点:")
      (command "insert" "border" "x" l1 "y" l2 "r" 0 pause)
      (setq p01 (getvar "lastpoint")
            p02 (polar p01 0 (+ (/ BB 2.0) (* 30 scale)))
            p02 (polar p02 pi09 (+ h1 h2 (* 100 factor) (* 40 scale)))
            p03 (polar p02 pi09 (+ (/ AA 2.0) (* 60 scale)))
      ) ;setq end
      (command "erase" "l" "")
      (pim p03)
      (pom p02)
   (setvar "dimlfac" 1.0)
   (command "layer" "s" "0" "")
   (setvar "dimlfac" 1)
) ;JC1 end
;
(defun C:ZJCS()
 (setq AA (getreal "\n锥形基础宽:(mm)")
       AA (* AA factor)
       BB (getreal "\n锥形基础长:(mm)")
       BB (* BB factor)
       b (getreal "\n柱高:(mm)")
       b (* b factor)
       h (getreal "\n柱宽:(mm)")
       h (* h factor)
 ) ;setq end       
  (princ "\n从下到上两级台阶高,用逗号隔开:(mm)")
  (load "tab.lsp")
  (setq scale factor)
  (setq l_th (readlh))
  (setq h1 (nth 1 l_th)
        h2 (nth 0 l_th)
        bg (getstring "\n锥形基础底标高:(m)")
  ) ;setq end       
  (setq scale (getvar "userr1"))
) ;defun ZJCS end
