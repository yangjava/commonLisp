(defun rs(ss n n1 / ll ll1 ind)
  (setq ss (rtos ss 2 n1)
        ll (strlen ss)
        ll1 (- n ll)
        ind 0
  ) ;setq end
  (while (< ind ll1)
     (setq ss (strcat " " ss)
           ind (1+ ind)
     ) ;setq end
  ) ;while end
  (setq ss ss)
) ;dedun end

(defun c:fb1()
 ;计算筏板底板配筋
 (setvar "cmdecho" 0)
  (textscr)
  (setq p0 (getreal "\np0(KN/m2):")
        lx (getreal "lx(m):")
        ly (getreal "ly(m):")
        ramda (/ ly lx)
        txt (strcat "ramda=" (rtos ramda 2 3))
   ) ;setq end
   (princ txt)
   (setq fx (getreal "\nfx:")
         fy (getreal "fy:")
         xx (getreal "xx:")
         yn (getstring "边跨(1)/中间跨(0):<0>")
	 b (getreal "基础梁宽(m):")
         h (getreal "底板厚(m):")
   	 h0 (- h 0.035)
         yn (if (= yn "") "0" yn)
         plx (* p0 lx lx)
         ply (* p0 ly ly)
         Mx (* fx plx)
         My (* fy ply)
         dMx (* 0.25 xx p0 lx b)
	 dMy (- 1 xx)
         dmy (* 0.25 dMy p0 ly b)
    ) ;setq end
    (if (= yn "1")
        (setq xx1 (getreal "第二跨xx:")
              aa1 (/ xx 16)
              aa2 (/ xx1 24)
              aa1 (+ aa1 aa2)
              M0x (* aa1 plx)
	      M0x (- M0x dMx)
              aa1 (/ (- 1 xx) 16)
  	      aa2 (/ (- 1 xx1) 24)
	      aa1 (+ aa1 aa2)
	      M0y (* aa1 ply)	
              M0y (- M0y dMy)
        ) ;setq end
        (setq M00x (* xx plx (/ 1 12.0))
              M00y (* (- 1 xx) ply (/ 1 12.0))
              M0x (- M00x dMx)
	      M0y (- M00y dMy)
        ) ;setq end
     ) ;if end
     (setq fac (* 0.9 310 h0 0.001)
           asx (/ Mx fac)
           asy (/ My fac)
 	   as0x (/ M0x fac)
	   as0y (/ M0y fac)
           txt1 (strcat "ly/lx=" (rs ramda 6 3) "  f5x=" (rs fx 6 4))
           txt2 (strcat "  f5y=" (rs fy 6 4)   "  x5x=" (rs xx 6 4))
           txt3 (strcat "   Mx=" (rs Mx 6 1)   "   My=" (rs My 6 1))
           txt4 (strcat "  Mx0=" (rs M00x 6 1) "  dMx=" (rs dMx 6 1))
           txt5 (strcat "  My0=" (rs M00y 6 1) "  dMy=" (rs dMy 6 1))
           txt6 (strcat " Mx0'=" (rs M0x 6 1)  " My0'=" (rs M0y 6 1))
           txt7 (strcat "  Asx=" (rs Asx 6 1)  "  Asy=" (rs Asy 6 1))
           txt8 (strcat " Asx0=" (rs As0x 6 1) " Asy0=" (rs As0y 6 1))
	)
	;(command "graghscr")
	(setq
           p1 (getpoint "\inpiute point:")
	   p2 (polar p1 pi27 400)
	   p3 (polar p2 pi27 400)
	   p4 (polar p3 pi27 400)
	   p5 (polar p4 pi27 400)
	   p6 (polar p5 pi27 400)
	   p7 (polar p6 pi27 400)
	   p8 (polar p7 pi27 400)
	   h 250
    ) ;setq end
    (command "text" p1 h 0 txt1)
    (command "text" p2 h 0 txt2)
    (command "text" p3 h 0 txt3)
    (command "text" p4 h 0 txt4)
    (command "text" p5 h 0 txt5)
    (command "text" p6 h 0 txt6)
    (command "text" p7 h 0 txt7)
    (command "text" p8 h 0 txt8)
) ;defun end
